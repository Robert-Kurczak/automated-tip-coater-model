import FreeCAD
from collections import Counter
import os.path

def getA2pObjects(document):
	found_objects = []

	for obj in document.Objects:
		if hasattr(obj, "objectType") and obj.objectType == "a2pPart":
			found_objects.append(obj)
			
	return found_objects

def getA2pObjectAbsolutePath(obj, doc):
	if os.path.isfile(obj.sourceFile):
		return obj.sourceFile
	else:
		return f"{os.path.dirname(doc.FileName)}/{obj.sourceFile}"

def resolveSubassemblies(a2p_objects):
	resolved_parts = []

	initial_doc = App.activeDocument()
	for obj in a2p_objects:
		obj_path = getA2pObjectAbsolutePath(obj, initial_doc)
		
		# TODO, reopening same document produces warnings
		obj_doc = App.openDocument(obj_path, True)
		
		if obj.subassemblyImport:
			child_objects = getA2pObjects(obj_doc)
			resolved_parts += resolveSubassemblies(child_objects)
		else:
			resolved_parts.append(obj_doc)

	return resolved_parts

class PartData:
	def __init__(self, part_doc):
		self.quantity = 1
		self.type = part_doc.Comment

def parsePartsToBomEntries(parts):
	part_count = {}
	for doc in parts:
		if doc.Label not in part_count:
			part_count[doc.Label] = PartData(doc)
		else:
			part_count[doc.Label].quantity += 1
			
	return part_count
	
def exportToCsv(parts_dict):
	doc = App.activeDocument()
	file_path = doc.FileName
	file_extension = file_path[file_path.rindex("."):]
	file_path = doc.FileName.replace(file_extension, "-bom.csv")
	
	with open(file_path, "w") as file:
		for part_name in sorted(parts_dict.keys()):
			part_data = parts_dict[part_name]
			
			file.write(f"{part_name};{part_data.type};{part_data.quantity}\n")
			
	return file_path

root_doc = App.activeDocument()
objects = getA2pObjects(root_doc)
objects = resolveSubassemblies(objects)
parts = parsePartsToBomEntries(objects)
bom_path = exportToCsv(parts)

root_doc_path = root_doc.FileName
for doc_name in App.listDocuments():
	App.closeDocument(doc_name)	
App.openDocument(root_doc_path)

print(f"Generated {bom_path}")
